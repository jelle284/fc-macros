from PySide import QtGui, QtCore

class MyButtons(QtGui.QDialog):
	""""""
	def __init__(self):
		super(MyButtons, self).__init__()
		self.initUI()
	def initUI(self):      
		replaceButton = QtGui.QPushButton("Replace All")
		replaceButton.clicked.connect(self.replace_all)
		self.searchLineEdit = QtGui.QLineEdit()
		self.replaceLineEdit = QtGui.QLineEdit()
		#
		mainLayout = QtGui.QVBoxLayout()
		mainLayout.addWidget(replaceButton)
		mainLayout.addWidget(QtGui.QLabel("Search for"))
		mainLayout.addWidget(self.searchLineEdit)
		mainLayout.addWidget(QtGui.QLabel("Replace with"))
		mainLayout.addWidget(self.replaceLineEdit)
		self.setLayout(mainLayout)
		# define window		xLoc,yLoc,xDim,yDim
		self.setGeometry(	250, 250, 0, 50)
		self.setWindowTitle("Search and replace in expressions")
		self.setWindowFlags(QtCore.Qt.WindowStaysOnTopHint)

	def replace_all(self):
		doc = App.ActiveDocument
		if not doc: return
		search_for = self.searchLineEdit.text()
		replace_with = self.replaceLineEdit.text()
		#find all objects with expressions
		expr_objs = [ob for ob in doc.Objects if ob.ExpressionEngine]
		#loop expressions
		count = 0
		for obj in expr_objs:
			print("working on", obj.Label)
			idxs = []
			for expr in obj.ExpressionEngine:
				k, v = expr
				if v.find(search_for) >= 0:
					obj.setExpression(k, v.replace(search_for, replace_with))
					count = count + 1
		QtGui.QMessageBox.information(None,"",f"{count} occurences replaced.")

form = MyButtons()
form.exec_()
