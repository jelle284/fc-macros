from mvc_gui import MVCGui
from PySide.QtWidgets import QDockWidget
import FreeCAD
import FreeCADGui
from PySide.QtCore import Qt

class MvcDockWidget(QDockWidget):
    def __init__(self):
        super(MvcDockWidget, self).__init__()
        self.setWindowTitle("Mini Version Control")
        appdata_path = FreeCAD.ConfigGet("UserAppData")
        self.mvc_gui = MVCGui(appdata_path)
        self.mvc_gui.register_file_handler("FCStd", FreeCAD.loadFile)
        self.setWidget(self.mvc_gui)

    def closeEvent(self, event):
        self.mvc_gui.timer.stop()
        super(MvcDockWidget, self).closeEvent(event)

if __name__ == "__main__":
    dock_widget = MvcDockWidget()
    FreeCADGui.getMainWindow().addDockWidget(Qt.RightDockWidgetArea, dock_widget)
